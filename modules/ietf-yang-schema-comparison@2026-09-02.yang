module ietf-yang-schema-comparison {
  yang-version 1.1;
  namespace "urn:ietf:params:xml:ns:yang:ietf-yang-schema-comparison";
  prefix yscmp;

  organization
    "IETF NETMOD (Network Modeling) Working Group";
  contact
    "WG List: NETMOD WG list <mailto:netmod@ietf.org>
     WG Web:  https://datatracker.ietf.org/wg/netmod

     Author:  Michal Vaško
              <mailto:mvasko@cesnet.cz>

     Author:  Rob Wilton
              <mailto:rwilton@cisco.com>

     Author:  Per Andersson
              <mailto:per.ietf@ionio.se>";
  description
    "This YANG 1.1 module contains extensions to support comparison
     between different versions of YANG schemas.

     Copyright (c) 2026 IETF Trust and the persons identified as
     authors of the code.  All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC XXXX
     (https://www.rfc-editor.org/info/rfcXXXX); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  // RFC Ed.: update the date below with the date of RFC publication
  // and remove this note.
  // RFC Ed.: replace XXXX (inc above) with actual RFC number and
  // remove this note.

  revision 2026-09-02 {
    description
      "Initial revision.";
    reference
      "RFC XXXX: YANG Schema Comparison";
  }

  extension ed-change-at {
    argument semver;
    description
      "Marks statements in the specified version of a module
       that introduces an editorial change of the statement.

       This extension may appear multiple times in a single
       statement and can also be combined with the other
       extensions in this module but each MUST always have
       a unique semver argument.

       Can only be a substatement of 'pattern', 'when',
       'must', 'description', 'reference', 'presence', or
       extension instance statements.";
    reference
      "RFC YYYY: YANG Semantic Versioning, section 4.4.";
  }

  extension bc-change-at {
    argument semver;
    description
      "Marks statements in the specified version of a module
       that introduces a backwards-compatible change of
       the statement.

       This extension may appear multiple times in a single
       statement and can also be combined with the other
       extensions in this module but each MUST always have
       a unique semver argument.

       Can only be a substatement of 'pattern', 'when',
       'must', 'description', 'reference', 'presence', or
       extension instance statements.";
    reference
      "RFC 7950: The YANG 1.1 Data Modeling Language, section 11.;
       RFC 6020: YANG - A Data Modeling Language for the Network
       Configuration Protocol (NETCONF), section 10.;
       RFC ZZZZ: Updated YANG Module Revision Handling, section 3.1.1.";
  }

  extension nbc-change-at {
    argument semver;
    description
      "Marks statements in the specified version of a module
       that introduces a non-backwards-compatible change of
       the statement.

       This extension may appear multiple times in a single
       statement and can also be combined with the other
       extensions in this module but each MUST always have
       a unique semver argument.

       Can only be a substatement of 'pattern', 'when',
       'must', 'description', 'reference', 'presence', or
       extension instance statements.";
    reference
      "RFC 7950: The YANG 1.1 Data Modeling Language, section 11.;
       RFC 6020: YANG - A Data Modeling Language for the Network
       Configuration Protocol (NETCONF), section 10.;
       RFC ZZZZ: Updated YANG Module Revision Handling, section 3.1.2.";
  }
}
