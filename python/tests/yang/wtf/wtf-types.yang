module wtf-types {
  namespace "urn:yang:wtf:types";
  prefix t;

  typedef str {
    type string;
  }

  typedef host {
    type str {
      pattern "[a-z]+";
    }
  }

  typedef unsigned {
    type union {
      type uint16;
      type uint32;
    }
  }

  typedef signed {
    type union {
      type int16;
      type int32;
    }
  }

  typedef number {
    type union {
      type unsigned;
      type signed;
    }
  }

  typedef protocol {
    type enumeration {
      enum http;
      enum https;
      enum ftp;
      enum sftp;
      enum tftp;
    }
  }

  typedef permissions {
    type bits {
      bit read;
      bit write;
      bit execute;
    }
  }
}
