module b {
  namespace "urn:b";
  prefix b_mod;

  include bsub;
  include btop;

  revision 2015-01-01 {
    description
      "version 1";
    reference "RFC XXXX";
  }

  feature foo;

  grouping gg {
    leaf bar-gggg {
      type string;
    }
  }

  container x {
    leaf bar-leaf {
      if-feature bar;
      type string;
    }
    uses gg {
      if-feature bar;
    }
    leaf baz {
      if-feature foo;
      type string;
    }
    leaf bubba {
      type string;
    }
  }
  augment "/x" {
    if-feature bar;
    container bar-y;
  }
  rpc bar-rpc {
    if-feature bar;
  }
  rpc foo-rpc {
    if-feature foo;
  }
}
