module mod8 {

    prefix abc;
    namespace "http://www.example.com";

    grouping gg {
        container cc {
            list ll {
                key a;
                typedef tt {
                    type string;
                }

                leaf a {
                    type tt;
                }
            }
        }
        typedef u {
            type uint8;
        }
    }
    grouping g {
        typedef gt {
            type string;
        }
        uses gg;
    }
    rpc rr {
      input {
        typedef aa {
            type uint32;
        }

        uses g;
      }
    }

    notification nn {
        typedef nt {
            type string {
                length "1..255";
            }
        }

        container log {
            leaf login {
                type nt;
            }
            leaf date {
                type string;
            }
        }
    }

    container ccc {
        uses g;
    }

    typedef tt {
        type boolean;
    }
}
