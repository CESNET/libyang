module mod2 {
   prefix abc;
   namespace "urn:cesnet:mod2";

   yang-version 1.1;
  
   list aa {
     key name;
     leaf name {
       type string;    
     }
    
    action act {
       reference "test reference";
       description "test description";    

       input {
         typedef in {
           type string;
         }
       }

       output {
         typedef out {
           type string;       
         }
      }
       
     }
   }   
}
