module mod5 {
    prefix abb;
    namespace "urn:cesnet:mod5";

    import mod {
        prefix mod;
    }

    include sub5;

    identity i1 {
        base mod:j2;
    }

    leaf-list llist {
        type identityref  {
            base mod:j2;
        }
    }

    leaf leaf {
        type identityref {
            base i1;
        }
    }

    leaf-list llist1 {
        type identityref {
            base sub_i3;
        }
    }

    leaf leaf2 {
        type identityref {
            base sub_i1;
        }
    }

    identity k2 {
        base k1;
    }

    identity k3 {
        base k2;
    }

    identity k1;

    leaf-list llist2 {
        type identityref {
            base k1;
        }
    }
}
