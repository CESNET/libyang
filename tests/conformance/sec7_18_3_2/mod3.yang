module mod3 {
    prefix abc;
    namespace "urn:cesnet:mod3";

    import mod {
        prefix mod;
    }

    deviation "/mod:cont" {
        description "test";

        deviate add {
            must "/llist";
        }

        deviate add {
            units "kilobyte";
        }
    }
}
