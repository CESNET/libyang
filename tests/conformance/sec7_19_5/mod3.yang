module mod3 {
    prefix acc;
    namespace "urn:cesnet:mod3";

    grouping login {
        container login {
            leaf user {
                type string;
            }

            leaf password {
                type string {
                    length "6..64";
                }
            }
        }
    }

    uses login {
        when "llist[.='42']";
        description "test";
    }

    list list {
        key keys;

        unique "login/user";

        leaf keys {
            type int32;
        }

        uses login {
            when "/ccc/test";
        }
    }

    container cont {
        uses server {
            when "../list_when[key1='1']";
        }
    }

    uses server {
        when "/ccc/test = 'true'";
    }

    container ccc {
        leaf test {
            type boolean;
        }
    }

    grouping server {
        container server {
            leaf ip {
                type string {
                    pattern '[0-9]+\.[0-9]+\.[0-9]+\.[0-9]+';
                }
            }
            leaf port {
                type uint16;
            }
        }
    }

    leaf-list llist {
        type uint8;
    }

    list list_when {
        key key1;

        leaf key1 {
            type uint8;
        }
    }
}
