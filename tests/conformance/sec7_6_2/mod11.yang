module mod11 {

    prefix abc;
    namespace "urn:cesnet:mod11";

    grouping login {
        leaf username {
            type string;
            description "test";
        }

        leaf password {
            type string;
            reference "test reference";
        }
    }

    feature f1;

    feature f3 {
        description "test";
    }

    container cont{

        leaf error{
            type uint8;
            default 0;
            reference "reference admin";
            description "description admin";
            units "count of failure interface";
            must "/interfaces/eth";
            must "../../username = 'admin' and /password";
            status current;
            when "../message";
        }

        container message {
            presence "enable counter of error";
        }

        list ll {
            key must;

            leaf weight {
                type uint32;
                units "kilogram";
            }

            leaf must {
                must "../../m = 'true'";
                type string;
            }
        }
        leaf m {
            if-feature f1;
            mandatory true;
            units "test";
            status obsolete;
            type boolean;
            if-feature f1;
        }

        leaf empty {
            type empty;
        }
    }

    uses login;

    leaf d {
        type decimal64 {
            fraction-digits 3;
        }
        default 3.141;
    }

    container interfaces {

        leaf-list eth {
            type boolean;
        }
        uses login;
    }
}
