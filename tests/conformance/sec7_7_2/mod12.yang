module mod12 {

    prefix abc;
    namespace "urn:cesnet:mod12";

    leaf-list users{
        type string;

        description "test1";
        reference "test2";

        status "deprecated";
    }

    feature f1;

    feature f2 {
        reference "abcdef";
    }

    typedef my {
        type string {
            length 1..255;
        }
    }
    container ccc {
        leaf-list leaf-lis1{
            type uint32;

            if-feature f2;

            must "../../user = 'Admin' and /password";

            must "../name = 'house'";

            if-feature f1;

            min-elements "0";
        }

        leaf name {
            type string;
        }

        choice ch1 {
            leaf-list l-l2 {
                type boolean;

                max-elements 10;

                units "test";
            }

            case abc {
                leaf-list l-l3 {
                    type my;

                    ordered-by system;

                    config "false";

                    reference "test";
                }

                leaf-list l-l4 {
                    type my {
                        pattern '[A-Za-z]+';
                    }

                    ordered-by user;

                    description "test";

                    reference "test2";

                    when "../name";

                    config true;

                    must "../../user = 'Admin'";

                    if-feature f2;

                    units "test units";

                    status current;

                    max-elements "unbounded";

                    min-elements "61";
                }

                container abc {
                    presence "enable";

                    container cc {
                        leaf-list l-l3 {
                            type my;

                            max-elements "100";

                            min-elements "61";

                            must "../../../../../user = 'Admin'";

                            config "true";
                        }


                    }
                }
            }
        }
    }

    leaf user {
        type string;
        default Admin;
    }

    leaf password {
        type string;
    }
}
