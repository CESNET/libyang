module annotations {
  namespace "urn:annot";
  prefix annot;
  yang-version 1.1;

  import ietf-yang-metadata {
    prefix md;
  }

  md:annotation id {
    type string;
  }

  container parrent {
    leaf-list child {
      type string;
    }
  }

  md:annotation abin {
    type binary;
  }

  md:annotation abits {
    type bits {
      bit CF;
      bit SF;
      bit OF;
    }
  }

  md:annotation abool {
    type boolean;
  }

  md:annotation adec {
    type decimal64 {
      fraction-digits 3;
    }
  }

  md:annotation aempty {
    type empty;
  }

  md:annotation aenum {
    type enumeration {
      enum zero;
      enum one;
    }
  }

  md:annotation aint8 {
    type int8;
  }

  md:annotation aint16 {
    type int16;
  }

  md:annotation aint32 {
    type int32;
  }

  md:annotation aint64 {
    type int64;
  }

  md:annotation auint8 {
    type uint8;
  }

  md:annotation auint16 {
    type uint16;
  }

  md:annotation auint32 {
    type uint32;
  }

  md:annotation auint64 {
    type uint64;
  }

  md:annotation astring {
    type string;
  }

  container annotations {
    list annot {
      key annoted-leaf;
      leaf annoted-leaf {
        type string;
      }
    }
  }

  container similar-annot-names {
    leaf-list l1leaf {
      type string;
    }

    container l2a {
      leaf-list l2aleaf {
        type uint32;
      }

      container l3aa {
        leaf-list l3aaleaf {
          type int8;
        }
      }
    }

    container l2b {
      leaf-list l2bleaf {
        type decimal64 {
          fraction-digits 2;
        }
      }
    }
  }

  md:annotation aaaa1 {
    type string;
  }

  md:annotation aaaa2 {
    type string;
  }

  md:annotation aaaa3 {
    type string;
  }

  md:annotation aaaa4 {
    type string;
  }

  md:annotation aaaa5 {
    type string;
  }

  md:annotation aaaa6 {
    type string;
  }

  md:annotation baaa1 {
    type string;
  }

  md:annotation baaa2 {
    type string;
  }

  md:annotation baaa3 {
    type string;
  }

  md:annotation baaa4 {
    type string;
  }

  md:annotation baaa5 {
    type string;
  }

  md:annotation baaa6 {
    type string;
  }
  md:annotation caaa1 {
    type string;
  }

  md:annotation caaa2 {
    type string;
  }

  md:annotation caaa3 {
    type string;
  }

  md:annotation caaa4 {
    type string;
  }

  md:annotation caaa5 {
    type string;
  }

  md:annotation caaa6 {
    type string;
  }

  md:annotation daaa1 {
    type string;
  }

  md:annotation daaa2 {
    type string;
  }

  md:annotation daaa3 {
    type string;
  }

  md:annotation daaa4 {
    type string;
  }

  md:annotation daaa5 {
    type string;
  }

  md:annotation daaa6 {
    type string;
  }
}
