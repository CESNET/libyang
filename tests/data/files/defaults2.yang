module defaults2 {
    namespace "urn:defaults2";
    prefix d;

    augment /d:oper/d:input/d:ch {
      container c1 {
        container c2 {
          leaf l {type string;}
        }
      }
    }

    list l1 {
        key "k";
        leaf k {
            type string;
        }

        container cont1 {
            container cont2 {
                leaf dflt1 {
                    type uint8;
                    default "10";
                }
            }
        }
    }

    leaf dflt2 {
        type string;
        when "/l1[k='when-true']";
        default "I exist!";
    }

    rpc oper {
      input {
        choice ch;
      }
    }

    rpc rpc1 {
      input {
        leaf l1 {
          type string;
        }
        leaf l2 {
          when "../l1='special-val'";
          type string;
          default "dflt";
        }
      }
    }
}
