module notif {
  yang-version 1.1;
  namespace "notif";
  prefix notif;
  
  container root {
    list list {
      key "name";

      leaf name {
        type string;
      }
      notification notif {
        leaf f1 {
          type string;
        }
      }
    }
  }
}
