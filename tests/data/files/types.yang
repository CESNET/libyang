module types {

  namespace "urn:ty";
  prefix types;
  yang-version 1.1;

  identity base-identity {
  }

  identity identity-for-ref {
    base base-identity;
  }

  container types {
    leaf bin {
      type binary;
    }

    leaf bits {
      type bits {
        bit CF {
          position 0;
        }

        bit OF {
          position 1;
        }
      }
    }

    leaf boolean-true {
      type boolean;
    }

    leaf boolean-false {
      type boolean;
    }

    leaf dec-zero {
      type decimal64 {
        fraction-digits 1;
      }
    }

    leaf dec-frac1-min {
      type decimal64 {
        fraction-digits 1;
      }
    }

    leaf dec-frac1-max {
      type decimal64 {
        fraction-digits 1;
      }
    }

    leaf dec-frac2-min {
      type decimal64 {
        fraction-digits 2;
      }
    }

    leaf dec-frac2-max {
      type decimal64 {
        fraction-digits 2;
      }
    }

    leaf dec-frac3-min {
      type decimal64 {
        fraction-digits 3;
      }
    }

    leaf dec-frac3-max {
      type decimal64 {
        fraction-digits 3;
      }
    }

    leaf dec-frac4-min {
      type decimal64 {
        fraction-digits 4;
      }
    }

    leaf dec-frac4-max {
      type decimal64 {
        fraction-digits 4;
      }
    }

    leaf dec-frac5-min {
      type decimal64 {
        fraction-digits 5;
      }
    }

    leaf dec-frac5-max {
      type decimal64 {
        fraction-digits 5;
      }
    }

    leaf dec-frac6-min {
      type decimal64 {
        fraction-digits 6;
      }
    }

    leaf dec-frac6-max {
      type decimal64 {
        fraction-digits 6;
      }
    }

    leaf dec-frac7-min {
      type decimal64 {
        fraction-digits 7;
      }
    }

    leaf dec-frac7-max {
      type decimal64 {
        fraction-digits 7;
      }
    }

    leaf dec-frac8-min {
      type decimal64 {
        fraction-digits 8;
      }
    }

    leaf dec-frac8-max {
      type decimal64 {
        fraction-digits 8;
      }
    }

    leaf dec-frac9-min {
      type decimal64 {
        fraction-digits 9;
      }
    }

    leaf dec-frac9-max {
      type decimal64 {
        fraction-digits 9;
      }
    }

    leaf dec-frac10-min {
      type decimal64 {
        fraction-digits 10;
      }
    }

    leaf dec-frac10-max {
      type decimal64 {
        fraction-digits 10;
      }
    }

    leaf dec-frac11-min {
      type decimal64 {
        fraction-digits 11;
      }
    }

    leaf dec-frac11-max {
      type decimal64 {
        fraction-digits 11;
      }
    }

    leaf dec-frac12-min {
      type decimal64 {
        fraction-digits 12;
      }
    }

    leaf dec-frac12-max {
      type decimal64 {
        fraction-digits 12;
      }
    }

    leaf dec-frac13-min {
      type decimal64 {
        fraction-digits 13;
      }
    }

    leaf dec-frac13-max {
      type decimal64 {
        fraction-digits 13;
      }
    }

    leaf dec-frac14-min {
      type decimal64 {
        fraction-digits 14;
      }
    }

    leaf dec-frac14-max {
      type decimal64 {
        fraction-digits 14;
      }
    }

    leaf dec-frac15-min {
      type decimal64 {
        fraction-digits 15;
      }
    }

    leaf dec-frac15-max {
      type decimal64 {
        fraction-digits 15;
      }
    }

    leaf dec-frac16-min {
      type decimal64 {
        fraction-digits 16;
      }
    }

    leaf dec-frac16-max {
      type decimal64 {
        fraction-digits 16;
      }
    }

    leaf dec-frac17-min {
      type decimal64 {
        fraction-digits 17;
      }
    }

    leaf dec-frac17-max {
      type decimal64 {
        fraction-digits 17;
      }
    }

    leaf dec-frac18-min {
      type decimal64 {
        fraction-digits 18;
      }
    }

    leaf dec-frac18-max {
      type decimal64 {
        fraction-digits 18;
      }
    }

    leaf empty {
      type empty;
    }

    leaf enum {
      type enumeration {
        enum zero;
        enum one;
        enum seven {
          value 7;
        }
      }
    }

    leaf identity-reference {
      type identityref {
        base base-identity;
      }
    }

    leaf instance-id {
      type instance-identifier;
    }

    leaf int8-min {
      type int8;
    }

    leaf int8-max {
      type int8;
    }

    leaf int16-min {
      type int16;
    }

    leaf int16-max {
      type int16;
    }

    leaf int32-min {
      type int32;
    }

    leaf int32-max {
      type int32;
    }

    leaf int64-min {
      type int64;
    }

    leaf int64-max {
      type int64;
    }

    leaf leaf-reference {
      type leafref {
        path "../int64-max";
      }
    }

    leaf string {
      type string;
    }

    leaf empty-string {
      type string;
    }

    leaf uint8-min {
      type uint8;
    }

    leaf uint8-max {
      type uint8;
    }

    leaf uint16-min {
      type uint16;
    }

    leaf uint16-max {
      type uint16;
    }

    leaf uint32-min {
      type uint32;
    }

    leaf uint32-max {
      type uint32;
    }

    leaf uint64-min {
      type uint64;
    }

    leaf uint64-max {
      type uint64;
    }
  }
}
