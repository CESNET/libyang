module sm-extension {
  yang-version 1.1;
  namespace "urn:sm-ext";
  prefix "sm-ext";

  import sm-modp {
    prefix modp;
  }

  list tlist {
    key "name";
    leaf name {
      type uint32;
    }
  }
  container tcont {
    leaf tleaf {
      type uint32;
    }
  }
}
