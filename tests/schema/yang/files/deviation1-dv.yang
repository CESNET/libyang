module deviation1-dv{

  namespace "urn:fri:params:xml:ns:yang:deviation1-dv";
  prefix dev1-dv;

  import deviation1 {
    prefix dev1;
  }

  description
    "This module contains a deviation which caused a double free crash...";

  deviation "/dev1:deviation1/dev1:cont"
          + "/dev1:cont-leaf" {
    description
      "Restrict the values for the c-tag cont to only allow 0x8100
       (33024) and 0x88A8 (34984).";
    deviate replace {
      type uint16 {
        range "33024 | 34984" {
          description
            "0x8100 | 0x88A8";
        }
      }
    }
  }
}
