submodule ext-inc {
  yang-version 1.1 {
    e:a;
    e:b "one";
    e:c "one";
  }
  belongs-to ext {
    e:a;
    e:b "one";
    e:c "one";
    prefix i {
      e:a;
      e:b "one";
      e:c "one";
    }
  }

  import ext-def {
    prefix e;
  }

  revision 2016-01-18;

  typedef mystring {
    type e:mystring;
  }

  leaf incleaf {
    type e:mystring;
  }
}
