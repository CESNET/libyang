module ext {
  yang-version 1.1;
  namespace "urn:ext";
  prefix e;

  import extimp {
    e:a;
    e:b "one";
    e:c "one";
    e:c "two" {
      e:a;
      e:b "one";
      e:c "one";
    }
    prefix i;
  }
  include ext-inc {
    e:a;
    e:b "one";
    e:c "one";
    e:c "two" {
      e:a;
      e:b "one";
      e:c "one";
    }
  }

  extension a;

  extension b {
    argument x;
  }

  extension c {
    argument y {
      yin-element true;
    }
  }

  extension d {
    e:a;
    e:b "one";
    e:c "one";
    e:c "two" {
      e:a;
      e:b "one";
      e:c "one";
    }
    argument z;
  }
  e:a;
  e:b "one";
  e:c "one";
  e:c "two" {
    e:a;
    e:b "one";
    e:c "one";
  }

  feature turbo {
    e:a;
    e:b "one";
    e:c "one";
    e:c "two" {
      e:a;
      e:b "one";
      e:c "one";
    }
  }

  identity id {
    e:a;
    e:b "one";
    e:c "one";
    e:c "two" {
      e:a;
      e:b "one";
      e:c "one";
    }
  }

  typedef etype {
    e:a;
    e:b "one";
    e:c "one";
    e:c "two" {
      e:a;
      e:b "one";
      e:c "one";
    }
    type string {
      e:a;
      e:b "one";
      e:c "one";
      e:c "two" {
        e:a;
        e:b "one";
        e:c "one";
      }
    }
  }

  grouping grp {
    e:a;
    e:b "one";
    e:c "one";
    e:c "two" {
      e:a;
      e:b "one";
      e:c "one";
    }
    leaf x {
      type string;
    }
  }

  container cont {
    e:a;
    e:b "one";
    e:c "one";
    e:c "two" {
      e:a;
      e:b "one";
      e:c "one";
    }
    list l {
      e:a;
      e:b "one";
      e:c "one";
      e:c "two" {
        e:a;
        e:b "one";
        e:c "one";
      }
      key "k";
      leaf k {
        type string;
      }
      action act {
        e:a;
        e:b "one";
        e:c "one";
        e:c "two" {
          e:a;
          e:b "one";
          e:c "one";
        }
      }
    }
    uses grp {
      e:a;
      e:b "one";
      e:c "one";
      e:c "two" {
        e:a;
        e:b "one";
        e:c "one";
      }
      refine "x" {
        e:a;
        e:b "one";
        e:c "one";
        e:c "two" {
          e:a;
          e:b "one";
          e:c "one";
        }
        default "none";
      }
    }
  }
  choice ch {
    e:a;
    e:b "one";
    e:c "one";
    e:c "two" {
      e:a;
      e:b "one";
      e:c "one";
    }
    case ch1 {
      e:a;
      e:b "one";
      e:c "one";
      e:c "two" {
        e:a;
        e:b "one";
        e:c "one";
      }
      leaf-list ch1ll {
        e:a;
        e:b "one";
        e:c "one";
        e:c "two" {
          e:a;
          e:b "one";
          e:c "one";
        }
        type string;
      }
    }
    anydata ch2 {
      e:a;
      e:b "one";
      e:c "one";
      e:c "two" {
        e:a;
        e:b "one";
        e:c "one";
      }
    }
  }
  augment "/cont" {
    e:a;
    e:b "one";
    e:c "one";
    e:c "two" {
      e:a;
      e:b "one";
      e:c "one";
    }
    leaf augleaf {
      e:a;
      e:b "one";
      e:c "one";
      e:c "two" {
        e:a;
        e:b "one";
        e:c "one";
      }
      type string;
    }
  }
  rpc op {
    e:a;
    e:b "one";
    e:c "one";
    e:c "two" {
      e:a;
      e:b "one";
      e:c "one";
    }
    input {
      e:a;
      e:b "one";
      e:c "one";
      e:c "two" {
        e:a;
        e:b "one";
        e:c "one";
      }
      leaf x {
        type string;
      }
    }
    output {
      e:a;
      e:b "one";
      e:c "one";
      e:c "two" {
        e:a;
        e:b "one";
        e:c "one";
      }
      leaf x {
        type string;
      }
    }
  }
  notification ntf {
    e:a;
    e:b "one";
    e:c "one";
    e:c "two" {
      e:a;
      e:b "one";
      e:c "one";
    }
  }
  deviation "/i:l" {
    e:a;
    e:b "one";
    e:c "one";
    e:c "two" {
      e:a;
      e:b "one";
      e:c "one";
    }
    deviate not-supported;
  }
}
