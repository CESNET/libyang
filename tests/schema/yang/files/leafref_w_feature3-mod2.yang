module leafref_w_feature3-mod2 {

  namespace "urn:fri:params:xml:ns:yang:leafref_w_feature3-mod2";
  prefix m2;

  import leafref_w_feature3-mod3 {
    prefix m3;
  }
    
  import leafref_w_feature3-mod4 {
    prefix m4;
  }
  
  augment "/m3:cont1" {
    container a_cont {
       leaf a_leaf {
         type m4:leafref_t1;
      }
    }
  }
}
