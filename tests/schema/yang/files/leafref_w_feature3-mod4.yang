module leafref_w_feature3-mod4 {

  namespace "urn:fri:params:xml:ns:yang:leafref_w_feature3-mod4";
  prefix m4;

  import leafref_w_feature3-mod3 {
    prefix m3;
  }

  typedef leafref_t1 {
    type leafref {
      path "/m3:cont1/m4:a_cont1/m4:a_leaf1";
    }
  }

  augment "/m3:cont1" {
    container a_cont1 {
      if-feature m3:feature1;
      leaf a_leaf1 {
        type string;
      }
    }
  }
}
