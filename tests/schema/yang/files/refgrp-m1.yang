module refgrp-m1 {

  namespace "urn:fri:params:xml:ns:yang:refgrp-m1";
  prefix rg-m1;

  import refgrp-m2 {
    prefix rg-m2;
  }

  import refgrp-m3 {
    prefix rg-m3;
  }

  notification ntf1 {
    uses rg-m2:ntf1 {
      refine choice1/case1/aleaf1 {
        default e1val1;
      }
    }
  }
}
