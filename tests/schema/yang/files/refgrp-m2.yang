module refgrp-m2 {

  namespace "urn:fri:params:xml:ns:yang:refgrp-m2";
  prefix rg-m2;

  import refgrp-m4 {
    prefix rg-m4;
  }

  typedef enum1 {
    type enumeration {
      enum e1val1 {
      }
      enum e1val2 {
      }
    }
  }

  grouping grp1 {
    leaf gleaf1 {
      type enum1;
      default e1val2;
    }
  }

  grouping ntf1 {
    uses rg-m4:grp1 {
      augment "choice1/case1" {
        uses rg-m2:grp1;
      }
    }
  }
}
