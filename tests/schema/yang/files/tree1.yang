module tree1 {
    namespace "urn:tree1";
    prefix t1;
   
    feature f1;
    grouping group1 {
        choice ch1 {
            case ca {
                leaf leaf1 {
                    if-feature f1;
                    type int8;
                }
            }
            default ca;
        }
        leaf leaf2 {
            type string;
        }
    }

    grouping group2 {
        leaf leaf3 {
            type string;
        }
    }

    choice x {
        leaf x {
            type string;
        }
    }

    container cont {
        leaf leaf4 {
            type uint8;
        }
        uses group2;
    }
    
    typedef type1 {
        type string;
    }
    
    anyxml any;
    rpc rpc1 {
        input {
            leaf in {
                type string;
            }
        }
        output {
            leaf out {
                type int8;
            }
        }
    }
    rpc rpc2;

    notification notif1;
    notification notif2;
}
