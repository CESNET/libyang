module enumeration {
    namespace "urn:test:enumeration";
    prefix enm;
    yang-version 1.1;

    revision 2000-01-02;

    leaf l1 {
        type enumeration {
            enum one;
            enum two;
            enum three;
            enum four;
            enum five;
        }
    }

    leaf l2 {
        type enumeration {
            enum a {
                value 1;
            }
            enum aa;
            enum b {
                value 5;
            }
            enum bb {
                value 8;
            }
            enum c {
                value 10;
            }
        }
    }
}
