module description {
    namespace "urn:test:description";
    prefix dsc;
    yang-version 1.1;

    revision 2000-01-01;

    leaf l1 {
        type uint16;
    }

    leaf l2 {
        type uint32;
        description "desc";
    }
}
