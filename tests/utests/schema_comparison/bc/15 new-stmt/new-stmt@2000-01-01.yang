module new-stmt {
    namespace "urn:test:new-stmt";
    prefix nst;
    yang-version 1.1;

    revision 2000-01-01;

    identity base-a;

    grouping top-grp {
        leaf gleaf {
            type uint32;
        }
    }

    grouping top-grp2;

    leaf l1 {
        type string;
    }

    uses top-grp2;

    rpc r1;
}
