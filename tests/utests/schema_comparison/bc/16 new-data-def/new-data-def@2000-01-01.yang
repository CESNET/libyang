module new-data-def {
    namespace "urn:test:new-data-def";
    prefix ndd;
    yang-version 1.1;

    revision 2000-01-01;

    container cont {
        leaf l1 {
            type string;
        }
    }
}
