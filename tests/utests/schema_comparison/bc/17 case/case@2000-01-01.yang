module case {
    namespace "urn:test:case";
    prefix cas;
    yang-version 1.1;

    revision 2000-01-01;

    choice ch {
        case c1 {
            leaf l1 {
                type string;
            }
        }
        case c3 {
            leaf l2 {
                type string;
            }
        }
    }
}
