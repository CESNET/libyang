module config {
    namespace "urn:test:config";
    prefix cfg;
    yang-version 1.1;

    revision 2000-01-01;

    container cont {
        leaf l1 {
            type string;
            config false;
        }
    }
}
