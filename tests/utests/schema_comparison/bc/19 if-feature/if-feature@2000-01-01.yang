module if-feature {
    namespace "urn:test:if-feature";
    prefix iff;
    yang-version 1.1;

    revision 2000-01-01;

    feature f;

    feature f2 {
        if-feature f;
    }

    identity id {
        if-feature f2;
    }

    typedef t1 {
        type enumeration {
            enum e1;
            enum e2 {
                if-feature f;
            }
        }
    }

    grouping grp {
        leaf l {
            if-feature "not f";
            type string;
        }
    }

    container cont {
        uses grp {
            if-feature "not f2";
        }
    }
}
