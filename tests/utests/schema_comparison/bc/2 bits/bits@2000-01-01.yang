module bits {
    namespace "urn:test:bits";
    prefix bts;
    yang-version 1.1;

    revision 2000-01-01;

    leaf l1 {
        type bits {
            bit one;
            bit two;
            bit three;
        }
    }

    leaf l2 {
        type bits {
            bit a {
                position 1;
            }
            bit b {
                position 5;
            }
            bit c {
                position 10;
            }
        }
    }
}
