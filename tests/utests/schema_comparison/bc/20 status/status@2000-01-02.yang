module status {
    namespace "urn:test:status";
    prefix sts;
    yang-version 1.1;

    revision 2000-01-02;

    container cont {
        leaf l1 {
            type string;
            status deprecated;
        }
        leaf l2 {
            type string;
            status deprecated;
        }
    }
}
