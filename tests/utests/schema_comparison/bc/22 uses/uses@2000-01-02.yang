module uses {
    namespace "urn:test:uses";
    prefix uss;
    yang-version 1.1;

    revision 2000-01-02;

    grouping grp {
        leaf l1 {
            type string {
                length 1..20;
            }
        }
    }

    uses grp;
}
