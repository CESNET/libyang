module length {
    namespace "urn:test:length";
    prefix lng;
    yang-version 1.1;

    revision 2000-01-01;

    typedef l1-type {
        type string {
            length min..10|20..50|100;
        }
    }

    leaf l1 {
        type l1-type;
    }

    leaf l2 {
        type string {
            length 0|100..200;
        }
    }

    leaf l3 {
        type string {
            length 10..20;
        }
    }
}
