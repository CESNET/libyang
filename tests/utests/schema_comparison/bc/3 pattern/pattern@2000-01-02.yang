module pattern {
    namespace "urn:test:pattern";
    prefix ptn;
    yang-version 1.1;

    import ietf-yang-schema-comparison {
        prefix schema-cmp;
    }

    revision 2000-01-02;

    leaf l1 {
        type string {
            pattern 'aa|bb|cc|dd|ee' {
                schema-cmp:backwards-compatible;
            }
        }
    }

    leaf l2 {
        type string;
    }
}
