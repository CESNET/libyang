module dflt {
    namespace "urn:test:dflt";
    prefix dfl;
    yang-version 1.1;

    revision 2000-01-01;

    typedef mytype {
        type string;
    }

    leaf l1 {
        type uint16;
    }

    leaf l2 {
        type mytype;
    }
}
