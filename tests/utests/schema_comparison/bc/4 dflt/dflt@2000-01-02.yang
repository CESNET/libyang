module dflt {
    namespace "urn:test:dflt";
    prefix dfl;
    yang-version 1.1;

    revision 2000-01-02;

    typedef mytype {
        type string;
        default "val";
    }

    leaf l1 {
        type uint16;
        default 10;
    }

    leaf l2 {
        type mytype;
    }
}
