module units {
    namespace "urn:test:units";
    prefix unt;
    yang-version 1.1;

    revision 2000-01-02;

    leaf l1 {
        type uint16;
        units "s";
    }

    leaf-list l2 {
        type string;
        units "packages";
    }
}
