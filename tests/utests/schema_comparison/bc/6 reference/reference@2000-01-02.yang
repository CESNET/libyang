module reference {
    namespace "urn:test:reference";
    prefix unt;
    yang-version 1.1;

    revision 2000-01-02;

    leaf l1 {
        type uint16;
        reference "some RFC";
    }

    leaf-list l2 {
        type string;
        reference "new RFC";
    }
}
