module must {
    namespace "urn:test:must";
    prefix mst;
    yang-version 1.1;

    import ietf-yang-schema-comparison {
        prefix schema-cmp;
    }

    revision 2000-01-02;

    leaf l1 {
        type uint16;
    }

    leaf l2 {
        type uint32;
        must ". > 30" {
            schema-cmp:bc-change-at 1.1.0;
        }
    }
}
