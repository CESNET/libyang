module when {
    namespace "urn:test:when";
    prefix whn;
    yang-version 1.1;

    import ietf-yang-schema-comparison {
        prefix schema-cmp;
    }

    revision 2000-01-02;

    leaf l1 {
        type uint16;
    }

    leaf l2 {
        type string;
        when "/l1 > 5" {
            schema-cmp:bc-change-at 1.1.0;
        }
    }
}
