module uses {
    namespace "urn:test:uses";
    prefix uss;
    yang-version 1.1;

    revision 2000-01-01;

    container cont1 {
        grouping grp {
            leaf l {
                type uint32;
            }
        }
        uses grp;
    }

    container cont2 {
        grouping grp {
            leaf l1 {
                type string {
                    length 1..20;
                }
            }
        }
        leaf l1 {
            type string {
                length 1..20;
            }
        }
    }

    grouping grp2 {
        leaf l2 {
            type string;
        }
    }

    uses grp2;
}
