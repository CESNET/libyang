module uses {
    namespace "urn:test:uses";
    prefix uss;
    yang-version 1.1;

    revision 2000-01-02;

    container cont1 {
        grouping grp {
            leaf l {
                type uint32;
            }
        }
        leaf l {
            type uint32;
        }
    }

    container cont2 {
        grouping grp {
            leaf l1 {
                type string {
                    length 1..20;
                }
            }
        }
        uses grp;
    }

    grouping grp2 {
        leaf l2 {
            type string;
        }
    }

    uses uss:grp2;
}
