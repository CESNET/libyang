module prefix {
    namespace "urn:test:prefix";
    prefix pfx;
    yang-version 1.1;

    revision 2000-01-01;

    identity ident1;

    grouping grp {
        container cont2 {
            leaf l1 {
                type string;
            }
        }
    }

    container cont {
        uses pfx:grp {
            augment "pfx:cont2" {
                leaf l2 {
                    type identityref {
                        base pfx:ident1;
                    }
                }
            }
        }
    }
}
