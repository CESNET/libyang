module type-imp {
    namespace "urn:test:type-imp";
    prefix typi;
    yang-version 1.1;

    revision 2000-01-02;

    typedef foreign-tpdf {
        type uint32 {
            range 10..10000;
        }
    }
}
