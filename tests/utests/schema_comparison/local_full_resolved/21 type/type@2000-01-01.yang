module type {
    namespace "urn:test:type";
    prefix typ;
    yang-version 1.1;

    import type-imp {
        prefix typi;
        revision-date 2000-01-01;
    }

    revision 2000-01-01;

    typedef local-tpdf {
        type uint8;
    }

    leaf l1 {
        type local-tpdf;
    }

    leaf l2 {
        type union {
            type typi:foreign-tpdf;
            type string;
        }
    }

    leaf l3 {
        type typi:foreign-tpdf;
    }
}
