module uses {
    namespace "urn:test:uses";
    prefix uss;
    yang-version 1.1;

    import uses-imp {
        prefix ussi;
        revision-date 2000-01-01;
    }

    revision 2000-01-01;

    leaf l1 {
        type string {
            length 1..20;
        }
    }

    uses ussi:foreign-group;
}
