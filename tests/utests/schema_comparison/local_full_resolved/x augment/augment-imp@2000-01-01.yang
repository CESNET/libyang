module augment-imp {
    namespace "urn:test:augment-imp";
    prefix augi;
    yang-version 1.1;

    revision 2000-01-01;

    grouping imp-group {
        container gcont {
            leaf gl {
                type string;
            }
        }
    }

    container cont {
        leaf l {
            type string;
        }
    }
}
