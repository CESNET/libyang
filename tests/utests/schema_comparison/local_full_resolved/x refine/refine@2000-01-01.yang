module refine {
    namespace "urn:test:refine";
    prefix rfn;
    yang-version 1.1;

    import refine-imp {
        prefix rfni;
        revision-date 2000-01-01;
    }

    revision 2000-01-01;

    grouping local-group {
        leaf ll {
            type uint32;
        }
    }

    container cont {
        uses rfni:foreign-group {
            refine fl {
                min-elements 5;
            }
        }
    }

    uses local-group {
        refine ll {
            default 500;
        }
    }
}
