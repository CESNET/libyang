module max-elements {
    namespace "urn:test:max-elements";
    prefix mxe;
    yang-version 1.1;

    revision 2000-01-02;

    leaf-list l1 {
        type uint16;
        max-elements 9;
    }

    list l2 {
        key "k";
        leaf k {
            type string;
        }
        max-elements 5;
    }
}
