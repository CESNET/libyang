module description {
    namespace "urn:test:description";
    prefix dsc;
    yang-version 1.1;

    revision 2000-01-01;

    leaf l1 {
        type uint16;
        description "is a nice leaf";
    }
}
