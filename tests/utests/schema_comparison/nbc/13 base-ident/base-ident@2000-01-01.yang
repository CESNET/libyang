module base-ident {
    namespace "urn:test:base-ident";
    prefix bai;
    yang-version 1.1;

    revision 2000-01-01;

    identity a;
    identity b {
        base a;
    }
    identity c {
        base a;
        base b;
    }
}
