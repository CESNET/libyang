module new-stmt {
    namespace "urn:test:new-stmt";
    prefix nst;
    yang-version 1.1;

    revision 2000-01-01;

    extension my-ext;

    feature feat1;

    identity base-a;

    grouping top-grp {
        leaf gleaf {
            type uint32;
        }
    }

    grouping top-grp2 {
        container cont {
            leaf lg {
                type uint8;
            }
        }
    }

    leaf l1 {
        type string;
    }

    uses top-grp2;
}
