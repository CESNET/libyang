module config {
    namespace "urn:test:config";
    prefix cfg;
    yang-version 1.1;

    revision 2000-01-02;

    container cont {
        leaf l1 {
            type string;
            mandatory true;
        }

        leaf l2 {
            type uint32;
            config false;
        }
    }
}
