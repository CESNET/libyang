module if-feature {
    namespace "urn:test:if-feature";
    prefix iff;
    yang-version 1.1;

    revision 2000-01-02;

    feature f;

    feature f2 {
        if-feature f;
    }

    identity id {
        if-feature f2;
    }

    typedef t1 {
        type enumeration {
            enum e1;
            enum e2;
        }
    }

    grouping grp {
        leaf l {
            type string;
            mandatory true;
        }
    }

    container cont {
        uses grp;
    }
}
