module status {
    namespace "urn:test:status";
    prefix sts;
    yang-version 1.1;

    revision 2000-01-02;

    container cont {
        leaf l1 {
            type string;
        }
        leaf l2 {
            type string;
            status obsolete;
        }
    }

    leaf l3 {
        type string;
        status current;
    }

    leaf l4 {
        type string;
        status deprecated;
    }
}
