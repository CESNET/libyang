submodule submod12 {
    belongs-to submod1 {
        prefix sm1;
    }
    yang-version 1.1;

    revision 2000-01-01;

    leaf l3 {
        type uint8;
    }

    leaf l4 {
        type string;
    }
}
