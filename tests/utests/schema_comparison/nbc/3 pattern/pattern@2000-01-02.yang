module pattern {
    namespace "urn:test:pattern";
    prefix ptn;
    yang-version 1.1;

    revision 2000-01-02;

    leaf l1 {
        type string {
            pattern 'aa|bb';
        }
    }

    leaf l2 {
        type string {
            pattern 'a|b|c';
        }
    }
}
