module range {
    namespace "urn:test:range";
    prefix rng;
    yang-version 1.1;

    revision 2000-01-02;

    leaf l1 {
        type uint16 {
            range 1..50|100;
        }
    }

    leaf l2 {
        type int32 {
            range -10..0|100|101;
        }
    }

    leaf l3 {
        type int8 {
            range -9..9;
        }
    }
}
