module dflt {
    namespace "urn:test:default";
    prefix dfl;
    yang-version 1.1;

    revision 2000-01-02;

    typedef mytype {
        type string;
    }

    leaf l1 {
        type uint16;
        default 100;
    }

    leaf l2 {
        type mytype;
    }
}
