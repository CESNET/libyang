module ext-inst {
    namespace "urn:test:ext-inst";
    prefix exi;
    yang-version 1.1;

    import ietf-yang-schema-comparison {
        prefix schema-cmp;
    }

    import "ietf-inet-types" {
        prefix inet {
            exi:ex "prefix-ext";
        }
        exi:ex "imp-ext";
    }

    reference "no-ref" {
        exi:ex "ref-ext";
    }

    revision 2000-01-02;

    feature f;

    identity id {
        exi:ex "id-ext" {
            schema-cmp:nbc-change-at 2.0.0;
        }
    }

    extension ex {
        argument name;
    }

    exi:ex "top-ext" {
        exi:ex "nested-top-ext";
    }

    leaf l {
        type enumeration {
            enum e1;
            enum e2;
        }
    }

    leaf k {
        type string {
            pattern 'a' {
                exi:ex "enum-ext";
            }
        }
    }
}
