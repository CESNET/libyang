module presence {
    namespace "urn:test:presence";
    prefix prs;
    yang-version 1.1;

    revision 2000-01-01;

    container con1 {
        presence "yes";
        leaf l1 {
            type string;
        }
    }

    container cont2;
}
