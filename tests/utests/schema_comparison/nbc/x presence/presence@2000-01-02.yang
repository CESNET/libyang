module presence {
    namespace "urn:test:presence";
    prefix prs;
    yang-version 1.1;

    revision 2000-01-02;

    container con1 {
        leaf l1 {
            type string;
        }
    }

    container cont2 {
        presence "yep";
    }
}
