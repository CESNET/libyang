module ietf-correct {
  yang-version 1.1;
  namespace "urn:ietf:params:xml:ns:yang:ietf-correct";
  prefix isc;

  organization
    "IETF NETMOD Working Group";

  contact
    "WG Web:   <https://datatracker.ietf.org/wg/netmod/>";

  description
    "Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.";

  revision 2026-07-08 {
    description
      "Initial revision.";
    reference
      "RFC XXXX: Test Module";
  }

  container system-info {
    description
      "A simple top-level container to hold our data. Notice it is
       not mandatory.";

    leaf system-name {
      type string;
      description
        "The configured name of the system.";
    }

    leaf status {
      type enumeration {
        enum active {
          description
            "The system is currently active and processing.";
        }
        enum inactive {
          description
            "The system is currently inactive.";
        }
      }
      description
        "The current operational status of the system. Notice there
         is no explicit 'config true' or 'mandatory false' here.";
    }
  }
}
