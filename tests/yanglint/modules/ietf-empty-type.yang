module ietf-empty-type {
  yang-version 1.1;
  namespace "urn:ietf:params:xml:ns:yang:ietf-empty-type";
  prefix eett;

  organization
    "IETF NETMOD (Network Modeling) Working Group";

  contact
    "WG Web:   <https://datatracker.ietf.org/wg/netmod/>
     WG List:  <mailto:netmod@ietf.org>

     Author:   Test Author
               <mailto:test@example.com>";

  description
    "Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.";

  revision 2026-07-10 {
    description
      "Initial revision. Testing empty types in keys and leaf-lists.";
    reference
      "RFC XXXX: Guidelines for Authors and Reviewers of YANG Data Models";
  }

  container top-container {
    description
      "A top level container to hold our test lists.";

    /* TEST 1: Trigger the 'empty' type in list key warning */
    list list-with-empty-key {
      key "id";
      description
        "A list to test the empty key warning.";

      /* TEST 2: Trigger the 'empty' type in leaf */
      leaf id {
        type empty;
        description
          "Key leaf of type empty.";
      }
    }

    /* TEST 3: Trigger the 'empty' type in leaf-list warning */
    leaf-list leaf-list-with-empty-type {
      type empty;
      description
        "A leaf-list to test the empty type warning.";
    }
  }
}
