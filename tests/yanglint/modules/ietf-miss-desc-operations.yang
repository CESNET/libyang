module ietf-miss-desc-operations {
  yang-version 1.1;
  namespace "urn:ietf:params:xml:ns:yang:ietf-miss-desc-operations";
  prefix desc-ops;

  organization "IETF NETMOD Working Group";
  contact "WG Web: <https://datatracker.ietf.org/wg/netmod/>";
  description
    "Copyright (c) 2026 IETF Trust and the persons identified as
    authors of the code.  All rights reserved.

    Redistribution and use in source and binary forms, with or
    without modification, is permitted pursuant to, and subject
    to the license terms contained in, the Revised BSD License
    set forth in Section 4.c of the IETF Trust's Legal Provisions
    Relating to IETF Documents
    (https://trustee.ietf.org/license-info).

    This version of this YANG module is part of RFC XXXX; see
    the RFC itself for full legal notices.";

  revision 2026-07-08 {
    description "Initial revision.";
    reference "RFC XXXX: Test Module";
  }

  rpc my-rpc {
    input {
      typedef in-type {
        type string;
      }
      leaf rpc-in {
        type string;
        description "Valid description to isolate the typedef/rpc errors.";
      }
    }
  }

  notification my-notif {
    leaf n-leaf {
      type string;
      description "Valid description to isolate the notification error.";
    }
  }

  list action-list {
    key "k2";
    description "Valid list description.";

    leaf k2 {
      type string;
      description "Valid key description.";
    }

    action my-act {
      input {
         leaf act-in {
           type string;
         }
      }
    }
  }
}
