module ietf-miss-desc-top-level {
  yang-version 1.1;
  namespace "urn:ietf:params:xml:ns:yang:ietf-miss-desc-top-level";
  prefix desc-top;

  organization "IETF NETMOD Working Group";
  contact "WG Web: <https://datatracker.ietf.org/wg/netmod/>";
  description
    "Copyright (c) 2026 IETF Trust and the persons identified as
    authors of the code.  All rights reserved.

    Redistribution and use in source and binary forms, with or
    without modification, is permitted pursuant to, and subject
    to the license terms contained in, the Revised BSD License
    set forth in Section 4.c of the IETF Trust's Legal Provisions
    Relating to IETF Documents
    (https://trustee.ietf.org/license-info).

    This version of this YANG module is part of RFC XXXX; see
    the RFC itself for full legal notices.";

  revision 2026-07-08 {
    description "Initial revision.";
    reference "RFC XXXX: Test Module";
  }

  extension ext1;

  feature feat1;

  identity id1;

  typedef top-type {
    type string;
  }

  grouping top-grp {
    leaf x {
      type string;
      description "Silencing internal grouping errors.";
    }
  }

  container cont {
    description "Dummy container for augment target.";
  }

  augment "/desc-top:cont" {
    // Top-level augment missing description
    leaf a-leaf {
      type string;
      description "Leaf desc";
    }
  }
}
