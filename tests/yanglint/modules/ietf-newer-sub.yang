submodule ietf-newer-sub {
  yang-version 1.1;
  belongs-to ietf-older-main {
    prefix om;
  }

  organization "IETF NETMOD Working Group";
  contact "WG Web: <https://datatracker.ietf.org/wg/netmod/>";
  description
    "Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG submodule is part of RFC XXXX; see
     the RFC itself for full legal notices.";

  revision 2026-07-08 {
    description "Newer revision.";
    reference "RFC XXXX";
  }
}
