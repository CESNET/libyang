module ietf-older-main {
  yang-version 1.1;
  namespace "urn:ietf:params:xml:ns:yang:ietf-older-main";
  prefix om;

  include ietf-newer-sub;
  import ietf-imported-module {
    prefix iim;
  }

  organization "IETF NETMOD Working Group";
  contact "WG Web: <https://datatracker.ietf.org/wg/netmod/>";
  description
    "Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.";

  // Triggers 4.7: Revision date is older than the submodule's date
  revision 2020-01-01 {
    description "Initial revision.";
    reference "RFC XXXX";
  }
}
