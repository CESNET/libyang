module ietf-xpath {
  yang-version 1.1;
  namespace "urn:ietf:params:xml:ns:yang:ietf-xpath";
  prefix ixt;

  organization "IETF NETMOD Working Group";

  contact
    "WG Web:   <https://datatracker.ietf.org/wg/netmod/>
     WG List:  <mailto:netmod@ietf.org>

     Author:   Test Author
               <mailto:test@example.com>";

  description
    "Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.";

  revision 2026-07-10 {
    description
      "Initial revision. Testing banned XPath functions and axes.";
    reference
      "RFC XXXX: Guidelines for Authors and Reviewers of YANG Data Models";
  }

  container top-container {
    description "A top level container to hold our test data.";

    /* TEST 1: Banned function 'local-name()' in a 'when' statement */
    container function-test-1 {
      when "local-name() = 'function-test-1'";
      description "Testing banned local-name() function.";
    }

    /*  TEST 2: Banned function 'position()' in a 'must' statement */
    list function-test-2 {
      key "id";
      must "position() < 10";
      description "Testing banned position() function.";

      leaf id {
        type string;
        description "Key leaf.";
      }
    }

    /* TEST 3: Banned axis 'preceding-sibling::' in a 'when' statement */
    leaf axis-test-1 {
      type string;
      when "preceding-sibling::function-test-2";
      description "Testing banned preceding-sibling axis.";
    }

    /* TEST 4: Banned axis 'following::' in a 'must' statement */
    leaf-list axis-test-2 {
      type string;
      must "following::ixt:axis-test-3 = 'test'";
      description "Testing banned following axis.";
    }

    leaf axis-test-3 {
      type string;
      description "Dummy node so the 'following' axis actually finds something.";
    }
  }
}
