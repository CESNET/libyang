module skeleton-augment {
  yang-version 1.1;
  namespace "urn:ietf:params:xml:ns:yang:skeleton-augment";
  prefix sa;

  import skeleton {
    prefix sc;
  }

  // Injects these nodes into the parent from a different module
  augment "/sc:main-box" {

    leaf aug-leaf {
      type string;
      default "augmented-value";
    }

    leaf-list aug-ll {
      type uint16;
      default 1;
      default 2;
    }
  }
}
